IIT-ALARMS-MIB DEFINITIONS ::= BEGIN

IMPORTS	enterprises
		FROM RFC1155-SMI
	OBJECT-TYPE
		FROM RFC1212
	TRAP-TYPE
		FROM RFC-1215;

--
-- Node definitions
--

-- 1.3.6.1.4.1.36220
iit OBJECT IDENTIFIER ::= { enterprises 36220 }

-- 1.3.6.1.4.1.36220.0
event_id OBJECT-TYPE
	SYNTAX OCTET STRING
	ACCESS read-only
	STATUS mandatory
	::= { iit 0 }

-- 1.3.6.1.4.1.36220.1
event_registration_time OBJECT-TYPE
	SYNTAX OCTET STRING
	ACCESS read-only
	STATUS mandatory
	::= { iit 1 }

-- 1.3.6.1.4.1.36220.2
rtu_title OBJECT-TYPE
	SYNTAX OCTET STRING
	ACCESS read-only
	STATUS mandatory
	::= { iit 2 }

-- 1.3.6.1.4.1.36220.3
trace_title OBJECT-TYPE
	SYNTAX OCTET STRING
	ACCESS read-only
	STATUS optional
	::= { iit 3 }

-- 1.3.6.1.4.1.36220.10
rtu_main_channel OBJECT-TYPE
	SYNTAX OCTET STRING
	ACCESS read-only
	STATUS optional
	::= { iit 10 }

-- 1.3.6.1.4.1.36220.11
rtu_reserve_channel OBJECT-TYPE
	SYNTAX OCTET STRING
	ACCESS read-only
	STATUS optional
	::= { iit 11 }


-- 1.3.6.1.4.1.36220.20
bop_title OBJECT-TYPE
	SYNTAX OCTET STRING
	ACCESS read-only
	STATUS optional
	::= { iit 20 }
	
-- 1.3.6.1.4.1.36220.21
bop_state OBJECT-TYPE
	SYNTAX OCTET STRING
	ACCESS read-only
	STATUS optional
	::= { iit 21 }
	
-- 1.3.6.1.4.1.36220.30
trace_state OBJECT-TYPE
	SYNTAX OCTET STRING
	ACCESS read-only
	STATUS optional
	::= { iit 30 }
	
-- 1.3.6.1.4.1.36220.31
accident_node_title OBJECT-TYPE
	SYNTAX OCTET STRING
	ACCESS read-only
	STATUS optional
	::= { iit 31 }
	
-- 1.3.6.1.4.1.36220.32
accident_type OBJECT-TYPE
	SYNTAX OCTET STRING
	ACCESS read-only
	STATUS optional
	::= { iit 32 }
	
-- 1.3.6.1.4.1.36220.33
accident_distance OBJECT-TYPE
	SYNTAX OCTET STRING
	ACCESS read-only
	STATUS optional
	::= { iit 33 }
		
-- 1.3.6.1.4.1.36220.34
accident_gps OBJECT-TYPE
	SYNTAX OCTET STRING
	ACCESS read-only
	STATUS optional
	::= { iit 34 }
	
-- 1.3.6.1.4.1.36220.40
left_node_title OBJECT-TYPE
	SYNTAX OCTET STRING
	ACCESS read-only
	STATUS optional
	::= { iit 40 }
	
-- 1.3.6.1.4.1.36220.41
left_node_gps OBJECT-TYPE
	SYNTAX OCTET STRING
	ACCESS read-only
	STATUS optional
	::= { iit 41 }
	
-- 1.3.6.1.4.1.36220.42
left_node_distance_to_rtu OBJECT-TYPE
	SYNTAX OCTET STRING
	ACCESS read-only
	STATUS optional
	::= { iit 42 }
	
-- 1.3.6.1.4.1.36220.50
right_node_title OBJECT-TYPE
	SYNTAX OCTET STRING
	ACCESS read-only
	STATUS optional
	::= { iit 50 }

	
-- 1.3.6.1.4.1.36220.51
right_node_gps OBJECT-TYPE
	SYNTAX OCTET STRING
	ACCESS read-only
	STATUS optional
	::= { iit 51 }
	
-- 1.3.6.1.4.1.36220.52
right_node_distance_to_rtu OBJECT-TYPE
	SYNTAX OCTET STRING
	ACCESS read-only
	STATUS optional
	::= { iit 52 }
	
-- 1.3.6.1.4.1.36220.60
base_ref_type OBJECT-TYPE
	SYNTAX OCTET STRING
	ACCESS read-only
	STATUS optional
	::= { iit 60 }

-- 1.3.6.1.4.1.36220.61
rtu_status_event_type OBJECT-TYPE
	SYNTAX OCTET STRING
	ACCESS read-only
	STATUS optional
	::= { iit 61 }

-- 1.3.6.1.4.1.36220.62
rtu_status_event_name OBJECT-TYPE
	SYNTAX OCTET STRING
	ACCESS read-only
	STATUS optional
	::= { iit 62 }
				
-- 1.3.6.1.4.1.36220.700
test_string OBJECT-TYPE
	SYNTAX OCTET STRING
	ACCESS read-only
	STATUS optional
	::= { iit 700 }
	
-- 1.3.6.1.4.1.36220.701
interger_number OBJECT-TYPE
	SYNTAX OCTET STRING
	ACCESS read-only
	STATUS optional
	::= { iit 701 }
	
-- 1.3.6.1.4.1.36220.702
floating_point_number OBJECT-TYPE
	SYNTAX OCTET STRING
	ACCESS read-only
	STATUS optional
	::= { iit 702 }
	

--
-- Trap definitions, Return
--

optical_event TRAP-TYPE
	ENTERPRISE iit
	VARIABLES { event_id, event_registration_time, rtu_title, trace_title, trace_state, 
		accident_node_title, accident_type, accident_distance, accident_gps, 
		left_node_title, left_node_gps, left_node_distance_to_rtu,
		right_node_title, right_node_gps, right_node_distance_to_rtu}
	::= 100

rtu_network_event TRAP-TYPE
	ENTERPRISE iit
	VARIABLES { event_id, event_registration_time, rtu_title, rtu_main_channel, rtu_reserve_channel }
	::= 200

bop_network_event TRAP-TYPE
	ENTERPRISE iit
	VARIABLES { event_id, event_registration_time, rtu_title, bop_title, bop_state }
	::= 300

rtu_status_event TRAP-TYPE
	ENTERPRISE iit
	VARIABLES { event_id, event_registration_time, rtu_title, trace_title, base_ref_type, rtu_status_event_type, rtu_status_event_name }
	::= 400

test_trap TRAP-TYPE
	ENTERPRISE iit
	VARIABLES { test_string, event_registration_time, interger_number, floating_point_number }
	::= 777


END
